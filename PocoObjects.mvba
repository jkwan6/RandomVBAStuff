Attribute VB_Name = "ElementParentChildWrapper"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
Option Explicit

Implements PocoObjectsInterface.IElementParentChildWrapper

Private NestedLevel As String
Private ParentID As Double
Private Level As String
Private ChildElement As Element


Private Property Get IElementParentChildWrapper_GetChildElement() As Element
    Set IElementParentChildWrapper_GetChildElement = ChildElement
End Property

Private Property Get IElementParentChildWrapper_GetLevel() As String
    IElementParentChildWrapper_GetLevel = Level
End Property

Public Property Get IElementParentChildWrapper_GetNestedDepth() As Integer
    IElementParentChildWrapper_GetNestedDepth = NestedLevel
End Property

Private Property Get IElementParentChildWrapper_GetParentID() As Double
    IElementParentChildWrapper_GetParentID = ParentID
End Property


Private Property Let IElementParentChildWrapper_LetChildElement(elementInput As Element)
    Set ChildElement = elementInput
End Property

Private Property Let IElementParentChildWrapper_LetLevel(RHS As String)
    Level = RHS
End Property

Private Property Let IElementParentChildWrapper_LetNestedDepth(RHS As Integer)
    NestedLevel = RHS
End Property

Private Property Let IElementParentChildWrapper_LetParentID(RHS As Double)
    ParentID = RHS
End Property

Attribute VB_Name = "Export"
Option Explicit

Public Function CreateElementParentChildWrapper() As PocoObjectsInterface.IElementParentChildWrapper
    Set CreateElementParentChildWrapper = New ElementParentChildWrapper
End Function

Public Function CreateLeaderWrapper() As PocoObjectsInterface.ILeaderWrapper
    Set CreateLeaderWrapper = New LeaderWrapper
End Function

Public Function CreateSignCodeWrapper() As PocoObjectsInterface.ISignCodeWrapper
    Set CreateSignCodeWrapper = New SignCodeWrapper
End Function

Public Function CreateSignFaceWrapper() As PocoObjectsInterface.ISignFaceWrapper
    Set CreateSignFaceWrapper = New SignFaceWrapper
End Function

Public Function CreateSignNumberWrapper() As PocoObjectsInterface.ISignNumberWrapper
    Set CreateSignNumberWrapper = New SignNumberWrapper
End Function

Public Function CreateSignSymbolWrapper() As PocoObjectsInterface.ISignSymbolWrapper
    Set CreateSignSymbolWrapper = New SignSymbolWrapper
End Function

Public Function CreateLevelMapper() As PocoObjectsInterface.ILevelMapper
    Set CreateLevelMapper = New LevelMapper
End Function

Attribute VB_Name = "LeaderWrapper"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements PocoObjectsInterface.ILeaderWrapper

Private StartPoint As Double
Private EndPoint As Double
Private NestedLevel As Integer
Private ParentID As Double
Private Level As String
Private LeaderElement As Element


Private Property Get ILeaderWrapper_GetEndPoint() As Double
    ILeaderWrapper_GetEndPoint = EndPoint
End Property
Private Property Get ILeaderWrapper_GetLeaderElement() As Element
    ILeaderWrapper_GetLeaderElement = LeaderElement
End Property
Private Property Get ILeaderWrapper_GetLevel() As String
    ILeaderWrapper_GetLevel = Level
End Property
Private Property Get ILeaderWrapper_GetNestedLevel() As Integer
    ILeaderWrapper_GetNestedLevel = NestedLevel
End Property
Private Property Get ILeaderWrapper_GetParentID() As Double
    ILeaderWrapper_GetParentID = ParentID
End Property
Private Property Get ILeaderWrapper_GetStartPoint() As Double
    ILeaderWrapper_GetStartPoint = StartPoint
End Property



Private Property Let ILeaderWrapper_LetEndPoint(RHS As Double)
    EndPoint = RHS
End Property
Private Property Let ILeaderWrapper_LetLeaderElement(RHS As Element)
    LeaderElement = RHS
End Property
Private Property Let ILeaderWrapper_LetLevel(RHS As String)
    Level = RHS
End Property
Private Property Let ILeaderWrapper_LetNestedLevel(RHS As String)
    NestedLevel = RHS
End Property
Private Property Let ILeaderWrapper_LetParentID(RHS As Double)
    ParentID = RHS
End Property
Private Property Let ILeaderWrapper_LetStartPoint(RHS As Double)
    StartPoint = RHS
End Property

Attribute VB_Name = "LevelMapper"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements PocoObjectsInterface.ILevelMapper

Private SignCodeLevel As String
Private SignFaceLevel As String
Private SignNumberLevel As String
Private SignSymbolLevel As String
Private LeaderLevel As String

Private Property Get ILevelMapper_GetLeaderLevel() As String
    ILevelMapper_GetLeaderLevel = LeaderLevel
End Property
Private Property Get ILevelMapper_GetSignCodeLevel() As String
    ILevelMapper_GetSignCodeLevel = SignCodeLevel
End Property
Private Property Get ILevelMapper_GetSignFaceLevel() As String
    ILevelMapper_GetSignFaceLevel = SignFaceLevel
End Property
Private Property Get ILevelMapper_GetSignNumberLevel() As String
    ILevelMapper_GetSignNumberLevel = SignNumberLevel
End Property
Private Property Get ILevelMapper_GetSignSymbolLevel() As String
    ILevelMapper_GetSignSymbolLevel = SignSymbolLevel
End Property


Private Property Let ILevelMapper_LetLeaderLevel(RHS As String)
    LeaderLevel = RHS
End Property
Private Property Let ILevelMapper_LetSignCodeLevel(RHS As String)
    SignCodeLevel = RHS
End Property
Private Property Let ILevelMapper_LetSignFaceLevel(RHS As String)
    SignFaceLevel = RHS
End Property
Private Property Let ILevelMapper_LetSignNumberLevel(RHS As String)
    SignNumberLevel = RHS
End Property
Private Property Let ILevelMapper_LetSignSymbolLevel(RHS As String)
    SignSymbolLevel = RHS
End Property

Attribute VB_Name = "SignFaceWrapper"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements PocoObjectsInterface.ISignFaceWrapper

Attribute VB_Name = "SignNumberWrapper"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements PocoObjectsInterface.ISignNumberWrapper
