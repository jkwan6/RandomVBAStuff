Attribute VB_Name = "IElementParentChildWrapper"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
Option Explicit


Public Property Get GetNestedDepth() As Integer
End Property
Public Property Get GetParentID() As Double
End Property
Public Property Get GetLevel() As String
End Property
Public Property Get GetChildElement() As Element
End Property


Public Property Let LetNestedDepth(nestedLevelInput As Integer)
End Property
Public Property Let LetParentID(idInput As Double)
End Property
Public Property Let LetLevel(levelInput As String)
End Property
Public Property Let LetChildElement(elementInput As Element)
End Property

Attribute VB_Name = "ILeaderWrapper"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
Option Explicit


Public Property Get GetStartPoint() As Double
End Property
Public Property Get GetEndPoint() As Double
End Property
Public Property Get GetNestedLevel() As Integer
End Property
Public Property Get GetParentID() As Double
End Property
Public Property Get GetLevel() As String
End Property
Public Property Get GetLeaderElement() As Element
End Property



Public Property Let LetStartPoint(startPointInput As Double)
End Property
Public Property Let LetEndPoint(endPointInput As Double)
End Property
Public Property Let LetNestedLevel(levelInput As String)
End Property
Public Property Let LetParentID(idInput As Double)
End Property
Public Property Let LetLevel(levelInput As String)
End Property
Public Property Let LetLeaderElement(leaderElementInput As Element)
End Property

Attribute VB_Name = "ILevelMapper"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
Option Explicit


Public Property Get GetSignCodeLevel() As String
End Property
Public Property Get GetSignFaceLevel() As String
End Property
Public Property Get GetSignSymbolLevel() As String
End Property
Public Property Get GetSignNumberLevel() As String
End Property
Public Property Get GetLeaderLevel() As String
End Property


Public Property Let LetSignCodeLevel(signCodeLevelInput As String)
End Property
Public Property Let LetSignFaceLevel(signFaceLevelInput As String)
End Property
Public Property Let LetSignSymbolLevel(signSymbolLevelInput As String)
End Property
Public Property Let LetSignNumberLevel(signNumberLevelInput As String)
End Property
Public Property Let LetLeaderLevel(leaderLevelInput As String)
End Property

Attribute VB_Name = "ISignCodeWrapper"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
Option Explicit


Public Property Get GetNestedLevel() As Integer
End Property
Public Property Get GetParentID() As Double
End Property
Public Property Get GetLevel() As String
End Property
Public Property Get GetChildElement() As Element
End Property


Public Property Let LetNestedLevel(nestedLevelInput As Integer)
End Property
Public Property Let LetParentID(parentIdInput As Double)
End Property
Public Property Let LetLevel(levelInput As String)
End Property
Public Property Let LetChildElement(childElementInput As Element)
End Property

Attribute VB_Name = "ISignSymbolWrapper"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
Option Explicit

Public NestedLevel As Integer
Public ParentID As Double
Public Level As String
Public Rotation As Double
Public SymbolElement As Element
